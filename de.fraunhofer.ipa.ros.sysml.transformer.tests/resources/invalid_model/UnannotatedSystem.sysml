// Copyright (c) 2022-2026 The CORESENSE Consortium. Apache License 2.0.

package UnannotatedModel {
    private import CSCore::*;

    part def UnannotatedSystem {
        part camera : CameraEngine;
        part detector : DetectorEngine;
    }
}
